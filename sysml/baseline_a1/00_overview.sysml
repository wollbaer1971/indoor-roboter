package MobileMaterialRobot_BaselineA1 {
  public import MobileMaterialRobot_Structure_A1::MobileMaterialRobot;
  public import MobileMaterialRobot_Context_A1::SystemContext;
  public import MobileMaterialRobot_Context_A1::schoolContext;
  public import MobileMaterialRobot_Requirements_A1::*;
  public import MobileMaterialRobot_Behavior_A1::*;
  public import MobileMaterialRobot_Interfaces_A1::*;
  public import MobileMaterialRobot_Verification_A1::*;
  public import MobileMaterialRobot_Simulation_A1::*;
  public import MobileMaterialRobot_SimulationVerification_A1::*;
  public import MobileMaterialRobot_ROS2Mapping_A1::*;
  public import MobileMaterialRobot_Views_A1::*;
  public import MobileMaterialRobot_Traceability_A1::*;
  public import MobileMaterialRobot_Decisions_A1::*;
  public import MobileMaterialRobot_Assumptions_A1::*;
  public import MobileMaterialRobot_NonGoals_A1::*;
  public import MobileMaterialRobot_Stakeholders_A1::*;
  doc /*
  Model: Mobile Material Robot - System Definition Baseline A.1
  Purpose:
    The Mobile Material Robot transports workpiece carriers of a transfer
    system autonomously between defined locations inside a production-like
    school demonstrator area.

  Method:
    This starter model follows the project documentation and keeps
    requirements, context, structure, interfaces, behavior, verification and
    ROS2 mapping traceable. Concrete technologies remain open unless they
    were explicitly decided in Baseline A.1.
  */
}
