package MobileMaterialRobot_Traceability_A1 {
  doc /*
  Planned responsibilities from the review matrix, now resolved model links.
  Dependencies do not assert requirement satisfaction or successful tests.
  Verification-to-requirement references are in 06_tests.sysml.
  */
  dependency from MobileMaterialRobot_Structure_A1::MissionSystem to MobileMaterialRobot_Requirements_A1::REQ_MIS_001;
  dependency from MobileMaterialRobot_Structure_A1::MissionSystem to MobileMaterialRobot_Requirements_A1::REQ_MIS_002;
  dependency from MobileMaterialRobot_Structure_A1::UserInterfaceSystem to MobileMaterialRobot_Requirements_A1::REQ_MIS_002;
  dependency from MobileMaterialRobot_Structure_A1::TransportSystem to MobileMaterialRobot_Requirements_A1::REQ_TRN_001;
  dependency from MobileMaterialRobot_Structure_A1::TransportSystem to MobileMaterialRobot_Requirements_A1::REQ_TRN_002;
  dependency from MobileMaterialRobot_Structure_A1::SafetySystem to MobileMaterialRobot_Requirements_A1::REQ_TRN_002;
  dependency from MobileMaterialRobot_Structure_A1::NavigationSystem to MobileMaterialRobot_Requirements_A1::REQ_MAP_001;
  dependency from MobileMaterialRobot_Structure_A1::PerceptionSystem to MobileMaterialRobot_Requirements_A1::REQ_MAP_002;
  dependency from MobileMaterialRobot_Structure_A1::NavigationSystem to MobileMaterialRobot_Requirements_A1::REQ_MAP_002;
  dependency from MobileMaterialRobot_Structure_A1::NavigationSystem to MobileMaterialRobot_Requirements_A1::REQ_MAP_003;
  dependency from MobileMaterialRobot_Structure_A1::NavigationSystem to MobileMaterialRobot_Requirements_A1::REQ_LOC_001;
  dependency from MobileMaterialRobot_Structure_A1::NavigationSystem to MobileMaterialRobot_Requirements_A1::REQ_NAV_001;
  dependency from MobileMaterialRobot_Structure_A1::MotionSystem to MobileMaterialRobot_Requirements_A1::REQ_NAV_001;
  dependency from MobileMaterialRobot_Structure_A1::NavigationSystem to MobileMaterialRobot_Requirements_A1::REQ_NAV_002;
  dependency from MobileMaterialRobot_Structure_A1::PerceptionSystem to MobileMaterialRobot_Requirements_A1::REQ_NAV_002;
  dependency from MobileMaterialRobot_Structure_A1::NavigationSystem to MobileMaterialRobot_Requirements_A1::REQ_NAV_003;
  dependency from MobileMaterialRobot_Structure_A1::MissionSystem to MobileMaterialRobot_Requirements_A1::REQ_NAV_003;
  dependency from MobileMaterialRobot_Structure_A1::NavigationSystem to MobileMaterialRobot_Requirements_A1::REQ_NAV_004;
  dependency from MobileMaterialRobot_Structure_A1::MotionSystem to MobileMaterialRobot_Requirements_A1::REQ_NAV_004;
  dependency from MobileMaterialRobot_Structure_A1::NavigationSystem to MobileMaterialRobot_Requirements_A1::REQ_NAV_005;
  dependency from MobileMaterialRobot_Structure_A1::MotionSystem to MobileMaterialRobot_Requirements_A1::REQ_NAV_005;
  dependency from MobileMaterialRobot_Structure_A1::SafetySystem to MobileMaterialRobot_Requirements_A1::REQ_SAFE_001;
  dependency from MobileMaterialRobot_Structure_A1::MotionSystem to MobileMaterialRobot_Requirements_A1::REQ_SAFE_001;
  dependency from MobileMaterialRobot_Structure_A1::SafetySystem to MobileMaterialRobot_Requirements_A1::REQ_SAFE_002;
  dependency from MobileMaterialRobot_Structure_A1::PerceptionSystem to MobileMaterialRobot_Requirements_A1::REQ_SAFE_002;
  dependency from MobileMaterialRobot_Structure_A1::UserInterfaceSystem to MobileMaterialRobot_Requirements_A1::REQ_UI_001;
  dependency from MobileMaterialRobot_Structure_A1::MissionSystem to MobileMaterialRobot_Requirements_A1::REQ_UI_001;
  dependency from MobileMaterialRobot_Structure_A1::UserInterfaceSystem to MobileMaterialRobot_Requirements_A1::REQ_UI_002;
  dependency from MobileMaterialRobot_Structure_A1::MissionSystem to MobileMaterialRobot_Requirements_A1::REQ_UI_002;
  dependency from MobileMaterialRobot_Structure_A1::EnergySystem to MobileMaterialRobot_Requirements_A1::REQ_UI_002;
  dependency from MobileMaterialRobot_Structure_A1::EnergySystem to MobileMaterialRobot_Requirements_A1::REQ_PWR_001;
  dependency from MobileMaterialRobot_Structure_A1::EnergySystem to MobileMaterialRobot_Requirements_A1::REQ_PWR_002;
  dependency from MobileMaterialRobot_Structure_A1::MotionSystem to MobileMaterialRobot_Requirements_A1::REQ_PERF_001;
  dependency from MobileMaterialRobot_Structure_A1::SafetySystem to MobileMaterialRobot_Requirements_A1::REQ_PERF_001;
  dependency from MobileMaterialRobot_Structure_A1::MissionSystem to MobileMaterialRobot_Requirements_A1::REQ_STA_001;
  dependency from MobileMaterialRobot_Structure_A1::UserInterfaceSystem to MobileMaterialRobot_Requirements_A1::REQ_STA_001;
  dependency from MobileMaterialRobot_Structure_A1::DiagnosticsSystem to MobileMaterialRobot_Requirements_A1::REQ_DIAG_001;
  dependency from MobileMaterialRobot_Structure_A1::CommunicationSystem to MobileMaterialRobot_Requirements_A1::REQ_DIAG_001;
  // Maintenance access concerns the physical robot as a whole; no
  // mechanical/electrical breakdown exists yet to allocate it more precisely.
  dependency from MobileMaterialRobot_Structure_A1::MobileMaterialRobot to MobileMaterialRobot_Requirements_A1::REQ_MNT_001;
  dependency from MobileMaterialRobot_Structure_A1::MissionSystem to MobileMaterialRobot_Requirements_A1::REQ_ARCH_003;
  dependency from MobileMaterialRobot_Structure_A1::NavigationSystem to MobileMaterialRobot_Requirements_A1::REQ_ARCH_003;
  dependency from MobileMaterialRobot_Structure_A1::CommunicationSystem to MobileMaterialRobot_Requirements_A1::REQ_ARCH_003;
}
